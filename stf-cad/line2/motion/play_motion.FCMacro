# STF-2 moving twin - FreeCAD macro.
# 1. Open STF2_Precise.FCStd (stf-factory/cad/line2_precise).  2. Macro -> Macros... -> play_motion.FCMacro
# A dock appears: slider (time), Play / Pause, speed, Reset (puts every part back where the CAD has it).
# The motion is NOT animated by hand: it is motion/timeline.json, generated by line2/motion.py from line_model
# (delta inverse kinematics, chain positions, stamp cycle, airlock exchange) and swept for collisions.
import os
import sys

import FreeCAD as App
import FreeCADGui as Gui

try:
    from PySide6 import QtCore, QtWidgets
except ImportError:
    from PySide2 import QtCore, QtWidgets

_here = None
for cand in [os.path.dirname(os.path.abspath(globals().get("__file__", ""))) if globals().get("__file__") else None,
             os.path.join(os.path.dirname(App.ActiveDocument.FileName), "motion") if App.ActiveDocument else None,
             App.getUserMacroDir(True)]:
    if cand and os.path.exists(os.path.join(cand, "motion_player.py")):
        _here = cand
        break
if _here is None:
    raise RuntimeError("motion_player.py not found next to the macro or in <document folder>/motion")
sys.path.insert(0, _here)
import importlib
import motion_player
importlib.reload(motion_player)

doc = App.ActiveDocument
if doc is None:
    raise RuntimeError("open STF2_Precise.FCStd first")
player = motion_player.Player(doc, motion_player.find_timeline(doc, _here))


class Dock(QtWidgets.QDockWidget):
    def __init__(self):
        super().__init__("STF-2 moving twin")
        w = QtWidgets.QWidget()
        lay = QtWidgets.QVBoxLayout(w)
        self.lbl = QtWidgets.QLabel(player.label(0))
        self.sl = QtWidgets.QSlider(QtCore.Qt.Horizontal)
        self.sl.setRange(0, player.n - 1)
        row = QtWidgets.QHBoxLayout()
        self.play = QtWidgets.QPushButton("Play")
        self.speed = QtWidgets.QDoubleSpinBox()
        self.speed.setRange(0.1, 10.0)
        self.speed.setValue(1.0)
        self.speed.setSuffix(" x")
        reset = QtWidgets.QPushButton("Reset")
        for x in (self.play, self.speed, reset):
            row.addWidget(x)
        lay.addWidget(self.lbl)
        lay.addWidget(self.sl)
        lay.addLayout(row)
        if player.missing:
            lay.addWidget(QtWidgets.QLabel(f"{len(player.missing)} timeline parts not in this document"))
        self.setWidget(w)
        self.timer = QtCore.QTimer()
        self.timer.timeout.connect(self.step)
        self.sl.valueChanged.connect(self.go)
        self.play.clicked.connect(self.toggle)
        reset.clicked.connect(self.reset)

    def go(self, k):
        player.apply(k)
        self.lbl.setText(player.label(k))
        Gui.updateGui()

    def step(self):
        self.sl.setValue((self.sl.value() + 1) % player.n)

    def toggle(self):
        if self.timer.isActive():
            self.timer.stop()
            self.play.setText("Play")
        else:
            self.timer.start(int(player.dt * 1000 / self.speed.value()))
            self.play.setText("Pause")

    def reset(self):
        self.timer.stop()
        self.play.setText("Play")
        player.reset()
        Gui.updateGui()

    def closeEvent(self, e):
        self.reset()
        super().closeEvent(e)


mw = Gui.getMainWindow()
for old in mw.findChildren(QtWidgets.QDockWidget, "stf2_motion"):
    old.close()
dock = Dock()
dock.setObjectName("stf2_motion")
mw.addDockWidget(QtCore.Qt.RightDockWidgetArea, dock)
dock.go(0)
